SSHKEY DEFINITIONS ::=
BEGIN

--
-- SSHKEY is a GSS-API mechanism that authenticates peers using SSH public
-- keys.  The corresponding Internet-Draft source is
-- draft-dowdeswell-kitten-gss-sshkey-00.xml.
--
-- Every SshKeyToken value is DER encoded.  The first token emitted by an
-- initiator that begins an exchange is additionally wrapped as the RFC 2743
-- InitialContextToken for this mechanism OID.  All other tokens are raw DER.
--

SshKeyCtx ::= SEQUENCE {
	  user	[0] OCTET STRING	OPTIONAL
	, key	[1] OCTET STRING	OPTIONAL
	, h	[2] OCTET STRING	OPTIONAL	-- rolling transcript hash
}

EncCtx ::= SEQUENCE {
	  encPart	[0] OCTET STRING
}

--
-- SshKeyUserAuth is DER encoded and encrypted into EncSshKeyUserAuth.
-- username contains the requested authorization identity.  sig proves
-- possession of the corresponding SSH user private key.  keytype is the SSH
-- public key algorithm name, key is the raw SSH public key blob, sigtype is
-- the SSH signature algorithm name, and sig is the SSH signature blob.  When
-- this mechanism is used for regular SSH login, username is the requested
-- local account selected by SSH userauth policy.
--
-- On successful authorization, the accepted GSS source name is the exact
-- requested username.  Its display form is username, and its exported name is
-- the RFC 2743 exported-name token for this mechanism OID with username as the
-- mechanism name payload.  The SSH key proves authorization for that account;
-- its fingerprint is not the GSS source name.
--
-- User authentication is not a distinct cleartext first-message step.
-- EncSshKeyUserAuth may appear in any token sent after the sender knows the
-- peer ECDH public key and can derive the exchange session key.  This lets
-- initiator-first exchanges keep the username encrypted without adding a
-- round trip, and lets acceptor-first exchanges carry encrypted userauth in
-- the initiator's first response.

SshKeyUserAuth ::= SEQUENCE {
	  username	[0] OCTET STRING
	, keytype	[1] OCTET STRING
	, key		[2] OCTET STRING
	, sigtype	[3] OCTET STRING
	, sig		[4] OCTET STRING
}

EncSshKeyUserAuth ::= OCTET STRING

--
-- SshKeyHostAuth proves possession of the acceptor host key.  keytype is the
-- SSH public key algorithm name, key is the raw SSH public key blob, sigtype
-- is an SSH signature algorithm name, and sig is the SSH signature blob.
-- The host signature authenticates the acceptor's ECDH contribution and the
-- associated algorithm and name context.

SshKeyHostAuth ::= SEQUENCE {
	  keytype	[0] OCTET STRING
	, key		[1] OCTET STRING
	, sigtype	[2] OCTET STRING
	, sig		[3] OCTET STRING
}

--
-- The initiator sends its supported signature algorithm names in sigtypes.
-- The acceptor replies with the signature algorithm names it is willing to
-- accept for user authentication.  SSH public key type and signature type are
-- separate because RSA public keys may be used with ssh-rsa, rsa-sha2-256, or
-- rsa-sha2-512 signatures.
--
-- The initiator tries configured key and signature-algorithm candidates in
-- OpenSSH order after it can derive the session key.  If a valid signature is
-- not authorized, the acceptor may return CONTINUE-NEEDED with the unchanged
-- encrypted server context, the original sigtypes list, and an authenticated
-- retry Finished.  The initiator verifies that proof before trying the next
-- candidate.  Invalid signatures and malformed exchanges are not retryable.
--
-- GSS does not require the initiator to produce the first token.  When
-- gss_accept_sec_context() is called with no input token, the acceptor sends
-- the same kind of KEX token as a signed challenge.  The initiator then
-- returns its KEX public key, the reflected encrypted server context, and
-- required encrypted userauth.  Context establishment fails if the initiator
-- cannot produce userauth or if the acceptor receives a final token without
-- it; this mechanism does not provide anonymous access.
--
-- HTTP Negotiate is a natural acceptor-first carrier: a server can include an
-- acceptor-first GSS-SSHKEY token in a 401 WWW-Authenticate header, and the
-- client can return its KEX public key, encrypted userauth, key confirmation,
-- and reflected sctx in the Authorization header.
--
-- The ECDH profile derives its base session key using the same
-- SP800-108 HMAC-SHA256 counter-mode KDF inputs as Heimdal SAnon-X25519:
--
--	K1	= raw X25519 shared secret
--	label	= "sanon-x25519"
--	context	= initiator-pk || acceptor-pk || uint32(0) ||
--		  uint32(flags) || canonical-channel-bindings
--	L	= 128 bits
--
-- canonical-channel-bindings is 0x00 when the caller supplies no bindings.
-- A present GSS channel-binding structure is encoded as 0x01 followed by the
-- initiator address type, initiator address length and bytes, acceptor address
-- type, acceptor address length and bytes, and application-data length and
-- bytes.  Every integer and length is an unsigned 32-bit little-endian value,
-- following the RFC 4121 channel-binding hash input.  Zero lengths remain in
-- the encoding, so a present empty structure is distinct from no bindings.
-- Every call for one context must supply the same canonical value.
--
-- SSHKEY currently sends no SAnon-style optional protocol flags, so flags is
-- zero.  The derived base session key is used for any further tokens including
-- userauth and gss_wrap/gss_unwrap, etc.
--
-- SSHKEY uses RFC 4121 CFX token framing for per-message tokens, but it is a
-- new mechanism and does not support Kerberos DES, Triple-DES, RC4, or other
-- legacy RFC 4121 encryption types.  The current enctype profile is
-- aes128-cts-hmac-sha256-128.
--
-- EncSshKeyUserAuth and sctx encPart contain ciphertext followed directly by
-- a 16-octet checksum.  They do not contain an enctype name or explicit nonce.
-- The encryption profile is RFC 8009 AES128-CTS-HMAC-SHA256-128 with key usage
-- 24, a random 16-octet confounder, and a field label prepended to the RFC 8009
-- integrity input as associated data.  The labels are "SSHKEY userauth v1" and
-- "SSHKEY server context v1", respectively.

SshKeyKEX ::= SEQUENCE {
	-- Negotiation part
	  kextypes	[0] OCTET STRING
	, enctypes	[1] OCTET STRING
	, sigtypes	[2] OCTET STRING

	-- Proposal part
	, kextype	[3] OCTET STRING	OPTIONAL
	, pk		[4] OCTET STRING	OPTIONAL
	, enctype	[5] OCTET STRING	OPTIONAL
	, nonce		[6] OCTET STRING	OPTIONAL
	-- Canonical host-based GSS target name.  Required whenever pk is present;
	-- omitted only from negotiation-only retry tokens.
	, acceptorName	[7] OCTET STRING	OPTIONAL
}

--
-- SshKeyFinished proves knowledge of the session key derived from the ECDH
-- exchange and transcript.  mac is computed with a key-confirmation key
-- derived from the exchange session key and covers the transcript hash, role,
-- and peer nonce.  An acceptor userauth-retry Finished instead covers the
-- original handshake hash, exact rejected encuserauth, unchanged sctx, retry
-- role, and initiator nonce.  It is not an SSH signature and does not require
-- another ssh-agent operation.

SshKeyFinished ::= SEQUENCE {
	  mac		[0] OCTET STRING
}

--
-- SshKeyServerContext is DER encoded and encrypted into SshKeyToken.sctx.
-- The client must return sctx unchanged with any continuation token so another
-- acceptor process with the same context-protection key can finish the
-- authentication.  The nonces are retained here so a stateless acceptor can
-- verify SshKeyFinished when the initiator returns.  issuedAt is a Unix time
-- in seconds.  The acceptor applies its local maximum-age policy to issuedAt.
-- This bounds the period in which reflected state can be accepted but does not
-- make it single-use.

SshKeyServerContext ::= SEQUENCE {
	  initiatorPk	[0] OCTET STRING	OPTIONAL
	, acceptorPk	[1] OCTET STRING
	, sessionKey	[2] OCTET STRING	OPTIONAL
	, initiatorSigtypes [3] OCTET STRING	OPTIONAL
	, acceptorSigtypes [4] OCTET STRING
	, acceptorSk	[5] OCTET STRING	OPTIONAL
	, initiatorNonce [6] OCTET STRING	OPTIONAL
	, acceptorNonce [7] OCTET STRING
	-- The canonical acceptor audience authenticated by this exchange.
	, acceptorName	[8] OCTET STRING
	, issuedAt	[9] INTEGER
}

--
-- XXXrcd: errors need to be expanded to some degree.

SshKeyStatus ::= INTEGER {
	  SSH-KEY-COMPLETE		(1)
	, SSH-KEY-CONTINUE-NEEDED	(2)
	, SSH-KEY-FAILURE		(3)
}

SshKeyToken ::= SEQUENCE {
	  status	[0] SshKeyStatus
	, kex		[1] SshKeyKEX		OPTIONAL
	, hostauth	[2] SshKeyHostAuth	OPTIONAL
	-- Required in an initiator's final COMPLETE token.  It remains optional
	-- in the shared envelope because earlier and acceptor tokens omit it.
	, encuserauth	[3] EncSshKeyUserAuth	OPTIONAL
	, cctx		[4] EncCtx		OPTIONAL
	, sctx		[5] EncCtx		OPTIONAL
	, finished	[6] SshKeyFinished	OPTIONAL
}

-- When a valid user signature is not authorized, an acceptor MAY return a
-- CONTINUE-NEEDED token containing only negotiation-form kex, the unchanged
-- sctx, and an acceptor userauth-retry Finished.  The initiator MUST verify
-- that proof against the exact attempt it just sent before trying the next
-- key and signature-algorithm candidate.  Invalid signatures and malformed
-- exchanges are not retryable.

--
-- XXXrcd: how about?
--
-- SshKeyMessage ::= SEQUENCE {
--	  status	[0] SshKeyStatus
--	, kex		[1] SshKeyKEX		OPTIONAL
--	, hostauth	[2] SshKeyHostAuth	OPTIONAL
--	, encuserauth	[3] EncSshKeyUserAuth	OPTIONAL
-- }
--
-- SshKeyMessage ::= CHOICE {
--	  plain		[0] SshKeyMessage
--	, encPart	[1] OCTET STRING	// just an encrypted plain
-- }
--
-- SshKeyToken ::= SEQUENCE {
--	  token		[0] SshKeyMessage
--	, cctx		[1] EncCtx		OPTIONAL
--	, sctx		[2] EncCtx		OPTIONAL
-- }

END
